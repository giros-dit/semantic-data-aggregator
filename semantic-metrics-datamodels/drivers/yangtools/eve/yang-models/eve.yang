module eve {

    yang-version 1.1;
    namespace 'http://data-aggregator.com/ns/eve';
    prefix "eve";

    organization "GIROS research group";

    contact "gi.giros@upm.es";

    description
        "YANG module to represent 5G-EVE records of metrics/KPIs.";

    reference
        "https://zenodo.org/record/3946323#.YIvPDqHtaUk";

    revision 2021-05-04 {
        description
            "Rename module. Remove list of records. Model invidual events from 5g-eve.";
        reference "0.2.0";
    }

    revision 2021-04-30 {
        description
            "Initial revision. Alignment with 5G-EVE data model as per
            deliverable D3.4: Second implementation of the interworking reference model.

            More details on 5G-EVE data model can be found in
            section 3.4.3.3: Information model to publish monitored data in the Monitoring platform.";
        reference "0.1.0";
    }

    grouping context-set {
        description
            "Optional. Context set associated with a record.";
        container labels {
            description
                "Enclosing container for the list of Labels
                associated with a record.";
            list label {
                key "name";
                description
                    "A name-value pair.";
                leaf name {
                    type string;
                    description
                        "Key of the label.";
                }
                leaf value {
                    type string;
                    mandatory true;
                    description
                        "Value of the label's key.";
                }
            }
        }
    }

    container eve-record {
        config false;
        description
            "Enclosing container for the record
            of a given metric/KPI in 5G-EVE.";
        leaf timestamp {
            type decimal64 {
                fraction-digits 6;
            }
            mandatory true;
            description
                "Time in which value has been captured.
                Unix epoch format with millisecond accuracy.";
        }
        leaf value {
            type decimal64 {
                fraction-digits 6;
            }
            mandatory true;
            description
                "Captured value for the specific metric/KPI.";
        }
        leaf unit {
            type string;
            mandatory true;
            description
                "Unit used in value.";
        }
        leaf device-id {
            type string;
            description
                "Identifies the device in which the record has been captured.";
        }
        uses context-set;
    }
}
