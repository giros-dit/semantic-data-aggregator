module logparser-vs {
    yang-version 1.1;
    namespace 'http://data-aggregator.com/ns/logparser/vs/metrics';
    prefix "logparser-vs-metrics";

    import ietf-yang-types { prefix ietf-types; }

    organization "GIROS research group";

    contact "gi.giros@upm.es";

    description
        "YANG module to represent the time-related metrics provided by the 5Growth Vertical Slircer (5Gr-VS) Log Management Tool during the network service instantiation and termination operations.";

    reference
        "5Growth WP4 deliverable D4.4: ... - section ... : ... .";

    revision 2021-09-27 {
        description
            "Initial revision. Alignment with 5Growth Vertical Slicer Log parser module data model for time-related metrics for the Instantiation CSMF Level Integration operation (INNOVALIA pilot).";
        reference "0.1.0";
    }

    identity metric-identity {
        description "An identity base for LogParser Vertical Slicer (VS) operation log metrics.";
    }
    
    /*** LogParser 5Gr-VS "Instantiation CSMF Level Integration" metrics for INNOVALIA pilot ***/

    identity Vertical_Service_Instantiation_Time {
        base metric-identity;
        description
            "Under discussion.";
    }
    
    identity EVE_VSS_Instantiation_Time {
        base metric-identity;
        description
            "Under discussion.";
    }
    
    identity EVE_VSS_Ready_Time {
        base metric-identity;
        description
            "Under discussion.";
    }  

    grouping metric-set {
        description
            "Metric set associated with a LogParser Vertical Slicer (VS) operation log.";
        container metrics {
            description
                "Enclosing container for the list of time-related metrics
                associated with a LogParser VS operation log.";
            list metric {
                key "name";
                description
                    "A name-value pair for the LogParser VS metrics.";
                leaf name {
                    type identityref {
                        base metric-identity;
                    }
                    description
                    "Key of the LogParser VS metric.";
                }
                leaf value {
                    type int64;
                    mandatory true;
                    description
                    "Value of the LogParser VS metric's key.";
                }
            }
        }
    }
    
    container logparser-vs-metrics {
        config false;
        description
            "Enclosing container for the time-related metrics provided by the 5Growth Vertical Slicer related logs during the network service instantiation and termination operations.";
        leaf Current_time {
            type ietf-types:date-and-time; 
            mandatory true;
            description
                "Date and time in which the time-related metric values have been collected (following the ISO 8601 format).";
        }
        leaf Operation {
            type enumeration {
                enum Instantiation_CSMF_Level_Integration;
            }
            mandatory true;
            description
                "Identifier of the type of operation (e.g., Instantiation_CSMF_Level_Integration).";
        }
        leaf VSI_ID {
            type string;
            mandatory true;
            description
                "Under discussion.";
        }
        leaf VSSI_ID {
            type string;  
            mandatory true;
            description
                "Under discussion.";
        }
        leaf VSB_ID {
            type string;  
            mandatory true;
            description
                "Under discussion.";
        }
        leaf Instance_Name {
            type string;  
            mandatory true;
            description
                "Under discussion.";
        }
        uses metric-set;
    }
}
