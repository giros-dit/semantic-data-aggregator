module logparser-so {

    yang-version 1.1;
    namespace 'http://data-aggregator.com/ns/logparser/so/metrics';
    prefix "logparser-so-metrics";

    import ietf-yang-types { prefix ietf-types; }

    organization "GIROS research group";

    contact "gi.giros@upm.es";

    description
        "YANG module to represent the time-related metrics provided by the 5Growth Service Orchestrator (5Gr-SO) Log Management Tool during the network service instantiation, scaling and termination operations.";

    reference
        "5Growth WP4 deliverable D4.3: 5G facility validation and verification report - section 2.2.1: Log Management Tool for 5Growth Service Orchestration.";

    revision 2021-09-27 {
        description
            "Initial revision. Alignment with 5Growth Service Orchestrator Log Parser module data model for time-related metrics during the 
            network service instantiation, scaling and termination operations.";
        reference "0.1.0";
    }

    identity metric-identity {
        description "An identity base for LogParser Service Orchestrator (SO) operation log metrics.";
    }
    
    /*** LogParser 5Gr-SO instantiation metrics ***/

    identity Total_Instantiation_Time {
        base metric-identity;
        description
            "Network service total instantiation time. The time it takes since the 5Gr-SO created the service identifier for a network service until it has been totally instantiated.";
    }
    
    identity Operation_ID_For_Instantiation_Op {
        base metric-identity;
        description
            "The time it takes the Northbound Interface (NBI) to generate an ID to identify the instantiation operation.";
    }
    
    identity ROE_Created_VLs {
        base metric-identity;
        description
            "Time in the interaction between Resource Orchestration Engine (ROE) and Resource Layer (RL) to allocate resources in the Logical Links (LLs) based on the ROE extract request.";
    } 
    
    identity ROE_Retrieve_RL_Resources {
        base metric-identity;
        description
            "The time to recollect the information from the Resource Layer (RL).";
    }
    
    identity ROE_Parsing_NSDs {
        base metric-identity;
        description
            "The time at Resource Orchestration Engine (ROE) submodule to parse NSD and VNFDs of an network service to get the required information for Placement Algorithm (PA).";
    }      
    
    identity ROE_Extract_VLs {
        base metric-identity;
        description
            "The time it takes the Resource Orchestration Engine (ROE) to determine the request of the different Virtual Links (VLs) needing resources in the Logical Links (LLs) because 
            connected VNFs have been deployed in multiple Virtualized Infrastructure Managers (VIMs).";
    }
    
    identity Retrieving_Descriptor_From_Catalogue_DBs {
        base metric-identity;
        description
            "The time to collect the descriptor from the network service descriptor (NSD) catalogue.";
    }
    
    identity PA_Calculation {
        base metric-identity;
        description
            "The time to build the request to the Placement Algorithm (PA), send it to the external PA service and receive its answers.";
    }      
    
    identity Create_Threshold_Based_Alerts {
        base metric-identity;
        description
            "Time interaction between SOE-SLA Manager modules of the 5Gr-SO to determine the threshold-alerts objects (if there is not AI/ML treatment) to be configured at the 5Gr-VoMS 
            plus the interaction to configure them at the 5GR-VoMs and receive the associated object identifiers and update the information in Network Service Instantiation Resource 
            (NSIR) database.";
    }
    
    identity Create_Monitoring_Jobs {
        base metric-identity;
        description
            "Time interaction between SOE-Monitoring Manager modules of 5Gr-SO to determine the monitoring jobs (exporters) and dashboards to be configured at the 5Gr-VoMS plus the interaction 
            to configure them and receive the associated object identifiers and update the information in Network Service Instantiation Resource (NSIR) database.";
    }      
    
    identity Create_AIML_Alerts {
        base metric-identity;
        description
            "Time interaction between SOE-SLA Manager to configure the AI/ML workflow to drive scaling operations. The creation and configuration of the data engineering pipeline consist of: 
            i) interaction with 5Gr-VoMs to create a Kafka Topic, ii) interaction with the 5Gr-AIML platform to download the required model, iii) creation of inference job at Apache Spark, 
            iv) update of Network Service Instantiation Resource (NSIR) database.";
    }  

    /*** LogParser 5Gr-SO termination metrics ***/
   
    identity Total_Termination_Time {
        base metric-identity;
        description
            "Network service total termination time. The time it takes to the 5Gr-SO to perform the termination operation since the request arrives to the Northbound Interface (NBI).";
    }

    identity Operation_ID_For_Termination_Op {
        base metric-identity;
        description
            "The time it takes the Northbound Interface (NBI) to generate an ID to identify the termination operation.";
    }
    
    identity ROE_Deleting_LLs {
        base metric-identity;
        description
            "Time in the Resource Orchestration Engine (ROE) to interact with the Resource Layer (RL) to deallocate resources in the logical links (LLs) serving the virtual link (VL) connections between VNFs deployed in multiple Virtualized Infrastructure Managers (VIMs).";
    } 
    
    identity Terminating_Threshold_Based_Alerts {
        base metric-identity;
        description
            "The time required in the interaction between Service Orchestration Engine (SOE) and SLA Manager to remove alert-based objects in case they have been configured in the 5Gr-VoMS.";
    }   
    
    identity Terminating_Monitoring_Jobs {
        base metric-identity;
        description
            "The time required in the interaction between Service Orchestration Engine (SOE) and Monitoring Manager to remove alert-based objects in case they have been configured in the 
            5Gr-VoMS.";
    }          
    
    identity Terminating_AIML_Alert_Jobs {
        base metric-identity;
        description
            "The time required in the interaction between Service Orchestration Engine (SOE) and SLA Manager to remove data engineering pipeline elements (Kafka topic, Spark job) in case 
            they have been configured in the 5Gr-VoMs and the Inference Platform (Apache Spark).";
    }
    
    /*** LogParser 5Gr-SO common metrics ***/

    identity SOE_Time {
        base metric-identity;
        description
            "Time spent in the Service Orchestration Engine (SOE) module (both at SOE parent, SOE child sub-modules) during the instantiation or termination process.";
    }
    
    identity ROE_Time {
        base metric-identity;
        description
            "Time spent in the Resource Orchestration Engine (ROE) module during the instantiation or termination process.";
    }

    identity Hierarchical_SOE_Dispatching_SOEpSOEc {
        base metric-identity;
        description
            "The time the hierarchical Service Orchestration Engine (SOE) uses to select the appropriate instantiation or termination process based on the nature of the service (single NS, composite NS).";
    }
    
    identity ROE_Updating_DBs {
        base metric-identity;
        description
            "Time to update databases (DBs) to declare the network service as operative and the instantiation or termination operation as successful.";
    }  

    identity CoreMANO_Wrapper_Time {
        base metric-identity;
        description
            "For instantiation operation: Time spent in the Core MANO Wrapper module during the instantiation process to create virtual network supporting the Virtual Links (VLs), the VMs supporting the VNFs, and 
            update the Network Service Instantiation Resource (NSIR) database. 
            For termination operation: Time spent in the Core MANO Wrapper module during the termination process to delete virtual network supporting the vitual links (VLs) and the VMs supporting the VNFs.";
    }

    grouping metric-set {
        description
            "Metric set associated with a LogParser Service Orchestrator (SO) operation log.";
        container metrics {
            description
                "Enclosing container for the list of time-related metrics
                associated with a LogParser SO operation log.";
            list metric {
                key "name";
                description
                    "A name-value pair for the LogParser Service Orchestrator (SO) metrics.";
                leaf name {
                    type identityref {
                        base metric-identity;
                    }
                    description
                    "Key of the LogParser SO metric.";
                }
                leaf value {
                    type int64;
                    mandatory true;
                    description
                    "Value of the LogParser SO metric's key.";
                }
            }
        }
    }
    
    container logparser-so-metrics {
        config false;
        description
            "Enclosing container for the time-related metrics provided by the 5Growth Service Orchestrator related logs during the network service instantiation, termination and scaling operations.";
        leaf Current_Time {
            type ietf-types:date-and-time; 
            mandatory true;
            description
                "Date and time in which the time-related metric values have been collected (following the ISO 8601 format).";
        }
        leaf Operation {
            type enumeration {
                enum instantiation;
                enum scaling;
                enum termination;
            }
            mandatory true;
            description
                "Identifier of the type of operation (i.e., instantiation, scaling or termination).";
        }
        leaf NS_ID {
            type string;
            mandatory true;
            description
                "Network Service Identifier.";
        }
        leaf NSD_ID {
            type string;  
            mandatory true;
            description
                "Network Service Descriptor Identifier.";
        }
        uses metric-set;
    }
}
