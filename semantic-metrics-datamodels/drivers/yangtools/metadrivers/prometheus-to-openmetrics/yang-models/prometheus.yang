module prometheus {

    yang-version 1.1;
    namespace 'http://data-aggregator.com/ns/prometheus';
    prefix "prom";

    organization "GIROS research group";

    contact "gi.giros@upm.es";

    description
        "YANG module to represent metrics collected from Prometheus HTTP API.";

    reference
        "https://prometheus.io/docs/prometheus/latest/querying/api/";


    revision 2021-11-18 {
        description
            "Initial revision.";
        reference "0.1.0";
    }

    grouping label-set {
        description
            "LabelSet associated with a Metric";
        container labels {
            description
                "Enclosing container for the list of Labels
                associated with a Metric";
            list label {
                key "name";
                description
                    "A name-value pair. These are used in multiple places:
                    identifying timeseries, value of INFO metrics,
                    and exemplars in Histograms";

                leaf name {
                    type string;
                    description
                        "Key of the label";
                }
                leaf value {
                    type string;
                    mandatory true;
                    description
                        "Value of the label's key";
                }
            }
        }
    }

    grouping metric-point-set {
        description
            "MetricPoints associated with a Metric";
        container metric-points {
            choice metric-points-choice {
                mandatory true;
                description
                    "Enclosing container for the list of MetricPoints
                    associated with a Metric";
                case metric-point-single {
                    description
                        "A MetricPoint in a Metric. If more than one MetricPoint
                        is exposed for a Metric, then its MetricPoints MUST have
                        monotonically increasing timestamps.";
                    leaf value {
                        type decimal64 {
                            fraction-digits 2;
                        }
                        mandatory true;
                        description
                            "Required. The value of the metric's sample";
                    }
                    leaf timestamp {
                        type decimal64 {
                            fraction-digits 3;
                        }
                        description
                            "Optional. The measurement timestamp of the metric's sample";
                    }
                }
                case metric-point-list {
                    list metric-point {
                        when "not(../metric-point)";
                        key "timestamp";
                        min-elements 2;
                        description
                            "A list of MetricPoints in a Metric. If more than one MetricPoint
                            is exposed for a Metric, then its MetricPoints MUST have
                            monotonically increasing timestamps.";
                        leaf value {
                            type decimal64 {
                                fraction-digits 2;
                            }
                            mandatory true;
                            description
                                "Required. The value of the metric's sample";
                        }
                        leaf timestamp {
                            type decimal64 {
                                fraction-digits 3;
                            }
                            mandatory true;
                            description
                                "Optional. The measurement timestamp of the metric's sample";
                        }
                    }
                }
            }
        }
    }

    container metrics {
        description
            "Enclosing container for the list of Prometheus metrics.";
        list metric {
            key "label-set-id";
            description
                "Metrics are defined by a unique LabelSet within a MetricFamily.
                Metrics MUST contain a list of one or more MetricPoints.
                Metrics with the same name for a given MetricFamily
                SHOULD have the same set of label names in their LabelSet.

                MetricPoints SHOULD NOT have explicit timestamps.

                If more than one MetricPoint is exposed for a Metric,
                then its MetricPoints MUST have monotonically increasing timestamps";

            leaf label-set-id {
                type string;
                description
                    "LabelSet ID that uniquely identifies a Metric within a MetricFamily.
                    Identifies generated from the calculated hash of the LabelSet dictionary.
                    Prometheus internally generates hashes in order to identify label sets.";
                reference
                    "https://github.com/prometheus/prometheus/blob/main/pkg/labels/labels.go";
            }

            leaf name {
                type string;
                mandatory true;
                description
                    "Name of the Metric. Combination of the MetricFamily's name plus
                    one of the available suffixes - if any - given the type of the Metric.
                    Suffixes for the respective types are:
                        Counter: '_total', '_created'
                        Summary: '_count', '_sum', '_created', '' (empty)
                        Histogram: '_count', '_sum', '_bucket', '_created'
                        GaugeHistogram: '_gcount', '_gsum', '_bucket'
                        Info: '_info'
                        Gauge: '' (empty)
                        StateSet: '' (empty)
                        Unknown: '' (empty)";
            }

            uses label-set;
            uses metric-point-set;
        }
    }
}
