module prometheus {

    yang-version 1.1;
    namespace 'http://data-aggregator.com/ns/prometheus';
    prefix "prom";

    organization "GIROS research group";

    contact "gi.giros@upm.es";

    description
        "YANG module to represent metrics collected from Prometheus HTTP API.";

    reference
        "https://prometheus.io/docs/prometheus/latest/querying/api/";

    revision 2021-05-04 {
        description
            "Initial revision.";
        reference "0.1.0";
    }

    grouping label-set {
        description
            "LabelSet associated with a Metric";
        container labels {
            description
                "Enclosing container for the list of Labels
                associated with a Metric";
            list label {
                key "name";
                description
                    "A name-value pair. These are used in multiple places:
                    identifying timeseries, value of INFO metrics,
                    and exemplars in Histograms";

                leaf name {
                    type string;
                    description
                        "Key of the label";
                }
                leaf value {
                    type string;
                    mandatory true;
                    description
                        "Value of the label's key";
                }
            }
        }
    }

    container metric {
        description
          "Enclosing container for a Prometheus metric.";
        leaf timestamp {
            type decimal64 {
                fraction-digits 3;
            }
			mandatory true;
            description
                "Optional. The measurement timestamp of the metric's sample";
        }
		leaf value {
            type decimal64 {
                fraction-digits 3;
            }
            mandatory true;
            description
                "Required. The value of the metric's sample";
        }
        leaf name {
            type string;
			mandatory true;
            description
                "Name of the Metric. Combination of the MetricFamily's name plus
                one of the available suffixes - if any - given the type of the Metric.
                Suffixes for the respective types are:
                    Counter: '_total', '_created'
                    Summary: '_count', '_sum', '_created', '' (empty)
                    Histogram: '_count', '_sum', '_bucket', '_created'
                    GaugeHistogram: '_gcount', '_gsum', '_bucket'
                    Info: '_info'
                    Gauge: '' (empty)
                    StateSet: '' (empty)
                    Unknown: '' (empty)";
        }
        uses label-set;
	}
}
